module net-topology {
    namespace "localhost:8300";

    prefix "net-topology";

    organization "<TBD> Inc.";

    contact
        "Instructor: AP
                    <Insert Contact Info Here>

        Developer:  DT
                    <Insert Contect Info Here>
                    
        Developer:  SR
                    <Insert Contact Info Here>
        ";

    description
        "This module is part of an assignment for CS158B,
         the goal is to familiarize ourselves with Netconf 
         and Yang. The Module is to model that of a NETWORK 
         TOPOLOGY which is a set of nodes where each node 
         is connected to a subset of the nodes.";

    revision 2016-12-03 {
        description "Initial revision";
    }

    typedef percent {
        type uint8 { range "0 .. 100";}
        description "Percentage";
    }

    typedef ip-v {
        type enumeration {
            enum "ipv4" {
            value 0;
            description
            "IPv4 protocol";
            }
        }
        description
        "Protocol versions";
    }

    typedef ipv4-address {
        type string {
            pattern '(([0-9]|[1-9][0-9]|1[0-9][0-9]|2[0-4][0-9]|25[0-5])\.){3}([0-9]|[1-9][0-9]|1[0-9][0-9]|2[0-4][0-9]|25[0-5])(%[\p{N}\p{L}]+)?';
        }
        description
        "Represents an IPv4 address";
    }

    typedef port-number {
        type uint16 {
            range "0..65535";
        }
    }

    grouping target-host {
        leaf host-name {
            type string;
            description "Systems hostname";
        }

        leaf address {
            type net-topology:ipv4-address;
        }

        leaf port {
            type net-topology:port-number;
        }

    }
	
    leaf-list cipher {
        type string;
    }

    list user {
        key "username";
        leaf username {
            type string;
        }
        leaf fullname {
            type string;
        }
    }   
    container host {
        uses target-host;
    }

    container network-objects {
        leaf obj1 {
            type int32;
        }
    }
}
